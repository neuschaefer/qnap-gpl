NSS322-MIB DEFINITIONS ::= BEGIN

   IMPORTS
      enterprises, Counter, TimeTicks
         FROM RFC1155-SMI
      OBJECT-TYPE
         FROM RFC-1212
      TRAP-TYPE
         FROM RFC-1215;

      -- From RFC-1213 (MIB-II)
      DisplayString ::=
         OCTET STRING

    cisco	OBJECT IDENTIFIER ::= { enterprises 9 }
    otherEnterprises	OBJECT IDENTIFIER ::= { cisco 6 }
    ciscoSB     OBJECT IDENTIFIER ::= { otherEnterprises 1 }
	nas004	OBJECT IDENTIFIER ::= { ciscoSB 103 }
    nss     OBJECT IDENTIFIER ::= { nas004 41 }
    nss322     OBJECT IDENTIFIER ::= { nss 322 }
    nssAthens MODULE-IDENTITY
          LAST-UPDATED "201103240000Z"
          ORGANIZATION  
          	 "Cisco Small Business"
          CONTACT-INFO
                 "Postal: 170 West Tasman Drive
                  San Jose, CA 95134-1706
                  USA
                  
                  Website:  Cisco Small Business Home <http://www.cisco.com/smb>
                  	    Cisco Small Business Support Community <http://www.cisco.com/go/smallbizsupport>"
          DESCRIPTION ""
          REVISION "201103240000Z"
          DESCRIPTION
                 "Initial revision."
	  ::= { nss322 114 }
    storageSystem        OBJECT IDENTIFIER ::= { nssAthens 1 }

 -- Frame Relay Multiplexer MIB groups
 -- system Event
   systemEventMsg        OBJECT IDENTIFIER ::= { storageSystem 1 }

 -- system event
   eventInformMsg OBJECT-TYPE
      SYNTAX  DisplayString
      ACCESS  read-only
      STATUS  current
      DESCRIPTION
         "Information event of NAS system."
     ::= { systemEventMsg 101 }

   eventWarningMsg OBJECT-TYPE
      SYNTAX  DisplayString
      ACCESS  read-only
      STATUS  current
      DESCRIPTION
         "Warning event of NAS system."
      ::= { systemEventMsg 102 }

   eventErrorMsg OBJECT-TYPE
      SYNTAX  DisplayString
      ACCESS  read-only
      STATUS  current
      DESCRIPTION
         "Error event of NAS system."
      ::= { systemEventMsg 103 }

	systemTraps OBJECT IDENTIFIER ::= { storageSystem  10 }
	
	eventInform TRAP-TYPE
		ENTERPRISE systemTraps    
		VARIABLES { eventInformMsg }
		DESCRIPTION
			"Info: %s"
		::=  1

	eventWarning TRAP-TYPE
		ENTERPRISE systemTraps    
		VARIABLES { eventWarningMsg }
		DESCRIPTION 
			"Warn: %s"
		::=  2

	eventError TRAP-TYPE
		ENTERPRISE systemTraps
		VARIABLES { eventErrorMsg }
		DESCRIPTION 
			"Error: %s"
		::=  4

 -- system inform
	systemInfo        OBJECT IDENTIFIER ::= { storageSystem 2 }

	systemCPU-Usage OBJECT-TYPE
		SYNTAX DisplayString
    	MAX-ACCESS read-only
	    STATUS     current
    	DESCRIPTION
			"System CPU usage"
		::= { systemInfo 1 }
	systemTotalMem OBJECT-TYPE
		SYNTAX DisplayString
    	MAX-ACCESS read-only
	    STATUS     current
    	DESCRIPTION
			"System total memory"
		::= { systemInfo 2 }
	systemFreeMem OBJECT-TYPE
		SYNTAX DisplayString
    	MAX-ACCESS read-only
	    STATUS     current
    	DESCRIPTION
			"System free memory"
		::= { systemInfo 3 }
	systemUptime OBJECT-TYPE
    	SYNTAX     TimeTicks
    	MAX-ACCESS read-only
	    STATUS     current
    	DESCRIPTION
        	"The amount of time since this host was last
	        initialized.  Note that this is different from
    	    sysUpTime in the SNMPv2-MIB [RFC1907] because
        	sysUpTime is the uptime of the network management
	        portion of the system."
    	::= { systemInfo 4 }
	cpu-Temperature OBJECT-TYPE
		SYNTAX DisplayString
    	MAX-ACCESS read-only
	    STATUS     current
    	DESCRIPTION
			"CPU temperature"
		::= { systemInfo 5 }
	systemTemperature OBJECT-TYPE
		SYNTAX DisplayString
    	MAX-ACCESS read-only
	    STATUS     current
    	DESCRIPTION
			"System temperature"
		::= { systemInfo 6 }

ifNumber OBJECT-TYPE
    SYNTAX  INTEGER
    ACCESS  read-only
    STATUS  mandatory
    DESCRIPTION
            "The number of network interfaces (regardless of
            their current state) present on this system."
    ::= { systemInfo 8 }
systemIfTable OBJECT-TYPE
    SYNTAX  SEQUENCE OF IfEntryDef
    ACCESS  not-accessible
    STATUS  mandatory
    DESCRIPTION
            "A list of interface entries.  The number of
            entries is given by the value of ifNumber."
    ::= { systemInfo 9 }
ifEntry OBJECT-TYPE
    SYNTAX  IfEntryDef
    ACCESS  not-accessible
    STATUS  mandatory
    DESCRIPTION
            "An interface entry containing objects at the
            subnetwork layer and below for a particular
            interface."
    INDEX   { ifIndex }
    ::= { systemIfTable 1 }
IfEntryDef ::=
    SEQUENCE {
        ifIndex
            INTEGER,
        ifDescr
            DisplayString,
		ifPacketsReceived
            Counter,
		ifPacketsSent
            Counter,
		ifErrorPackets
            Counter
	}
ifIndex OBJECT-TYPE
    SYNTAX  INTEGER
    ACCESS  read-only
    STATUS  mandatory
    DESCRIPTION
            "A unique value for each interface.  Its value
            ranges between 1 and the value of ifNumber.  The
            value for each interface must remain constant at
            least from one re-initialization of the entity's
            network management system to the next re-
            initialization."
    ::= { ifEntry 1 }
ifDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { ifEntry 2 }
ifPacketsReceived OBJECT-TYPE
    SYNTAX  Counter
    ACCESS  read-only
    STATUS  mandatory
    DESCRIPTION
            "System packets received."
    ::= { ifEntry 3 }
ifPacketsSent OBJECT-TYPE
    SYNTAX  Counter
    ACCESS  read-only
    STATUS  mandatory
    DESCRIPTION
            "System packets sent."
    ::= { ifEntry 4 }
ifErrorPackets OBJECT-TYPE
    SYNTAX  Counter
    ACCESS  read-only
    STATUS  mandatory
    DESCRIPTION
            "System error packets."
    ::= { ifEntry 5 }

hdNumber OBJECT-TYPE
    SYNTAX  INTEGER
    ACCESS  read-only
    STATUS  mandatory
    DESCRIPTION
            "The number of hard disk (regardless of
            their current state) present on this system."
    ::= { systemInfo 10 }
systemHdTable OBJECT-TYPE
    SYNTAX  SEQUENCE OF HdEntryDef
    ACCESS  not-accessible
    STATUS  mandatory
    DESCRIPTION
            "A list of interface entries.  The number of
            entries is given by the value of ifNumber."
    ::= { systemInfo 11 }
hdEntry OBJECT-TYPE
    SYNTAX  HdEntryDef
    ACCESS  not-accessible
    STATUS  mandatory
    DESCRIPTION
            "An interface entry containing objects at the
            subnetwork layer and below for a particular
            interface."
    INDEX   { hdIndex }
    ::= { systemHdTable 1 }
HdEntryDef ::=
    SEQUENCE {
        hdIndex
            INTEGER,
        hdDescr
            DisplayString,
        hdTemperature
            DisplayString,
        hdStatus
            INTEGER,
	hdModel DisplayString,
	hdCapacity DisplayString,
	hdSmartInfo DisplayString
	}
hdIndex OBJECT-TYPE
    SYNTAX  INTEGER
    ACCESS  read-only
    STATUS  mandatory
    DESCRIPTION
            "A unique value for each hard disk.  Its value
            ranges between 1 and the value of ifNumber.  The
            value for each interface must remain constant at
            least from one re-initialization of the entity's
            network management system to the next re-
            initialization."
    ::= { hdEntry 1 }
hdDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { hdEntry 2 }
hdTemperature OBJECT-TYPE
    SYNTAX  DisplayString
    ACCESS  read-only
    STATUS  mandatory
    DESCRIPTION
            "Hard disk temperature."
    ::= { hdEntry 3 }
hdStatus OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { hdEntry 4 }
hdModel OBJECT-TYPE
    SYNTAX  DisplayString
    ACCESS  read-only
    STATUS  mandatory
    DESCRIPTION "Hard disk model."
    ::= { hdEntry 5 }
hdCapacity OBJECT-TYPE
    SYNTAX  DisplayString
    ACCESS  read-only
    STATUS  mandatory
    DESCRIPTION "Hard disk capacity."
    ::= { hdEntry 6 }
hdSmartInfo OBJECT-TYPE
    SYNTAX  DisplayString
    ACCESS  read-only
    STATUS  mandatory
    DESCRIPTION "Hard disk SMART information."
    ::= { hdEntry 7 }

	modelName OBJECT-TYPE
		SYNTAX DisplayString
    	MAX-ACCESS read-only
	    STATUS     current
    	DESCRIPTION
			"Model name"
		::= { systemInfo 12 }
	hostName OBJECT-TYPE
		SYNTAX DisplayString
    	MAX-ACCESS read-only
	    STATUS     current
    	DESCRIPTION
			"Model name"
		::= { systemInfo 13 }

sysFanNumber OBJECT-TYPE
    SYNTAX  INTEGER
    ACCESS  read-only
    STATUS  mandatory
    DESCRIPTION
            "The number of system fan (regardless of
            their current state) present on this system."
    ::= { systemInfo 14 }
systemFanTable OBJECT-TYPE
    SYNTAX  SEQUENCE OF SysFanEntryDef
    ACCESS  not-accessible
    STATUS  mandatory
    DESCRIPTION
            "A list of interface entries.  The number of
            entries is given by the value of sysFanNumber."
    ::= { systemInfo 15 }
sysFanEntry OBJECT-TYPE
    SYNTAX  SysFanEntryDef
    ACCESS  not-accessible
    STATUS  mandatory
    DESCRIPTION
            "An system fan entry containing objects at the
            subnetwork layer and below for a particular
            interface."
    INDEX   { sysFanIndex }
    ::= { systemFanTable 1 }
SysFanEntryDef ::=
    SEQUENCE {
        sysFanIndex
            INTEGER,
        sysFanDescr
            DisplayString,
		sysFanSpeed
            DisplayString
	}
sysFanIndex OBJECT-TYPE
    SYNTAX  INTEGER
    ACCESS  read-only
    STATUS  mandatory
    DESCRIPTION
            "A unique value for each system fan. Its value
            ranges between 1 and the value of sysFanNumber.  The
            value for each interface must remain constant at
            least from one re-initialization of the entity's
            network management system to the next re-
            initialization."
    ::= { sysFanEntry 1 }
sysFanDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { sysFanEntry 2 }
sysFanSpeed OBJECT-TYPE
    SYNTAX  DisplayString (SIZE (0..255))
    ACCESS  read-only
    STATUS  mandatory
    DESCRIPTION
            "System fan speed."
    ::= { sysFanEntry 3 }

sysVolumeNumber OBJECT-TYPE
    SYNTAX  INTEGER
    ACCESS  read-only
    STATUS  mandatory
    DESCRIPTION
            "The number of system volumes (regardless of
            their current state) present on this system."
    ::= { systemInfo 16 }
systemVolumeTable OBJECT-TYPE
    SYNTAX  SEQUENCE OF SysVolumeEntryDef
    ACCESS  not-accessible
    STATUS  mandatory
    DESCRIPTION
            "A list of volume entries.  The number of
            entries is given by the value of sysVolumeNumber."
    ::= { systemInfo 17 }
sysVolumeEntry OBJECT-TYPE
    SYNTAX  SysVolumeEntryDef
    ACCESS  not-accessible
    STATUS  mandatory
    DESCRIPTION
            "An system volume entry"
    INDEX   { sysVolumeIndex }
    ::= { systemVolumeTable 1 }
SysVolumeEntryDef ::=
    SEQUENCE {
        sysVolumeIndex	INTEGER,
        sysVolumeDescr	DisplayString,
	sysVolumeFS	DisplayString,
	sysVolumeTotalSize	DisplayString,
	sysVolumeFreeSize	DisplayString,
	sysVolumeStatus	DisplayString
	}
sysVolumeIndex OBJECT-TYPE
    SYNTAX  INTEGER
    ACCESS  read-only
    STATUS  mandatory
    DESCRIPTION
            "A unique value for each system volume. Its value
            ranges between 1 and the value of sysVolumeNumber.  The
            value for each volume must remain constant at
            least from one re-initialization of the entity's
            volume system to the next re-initialization."
    ::= { sysVolumeEntry 1 }
sysVolumeDescr OBJECT-TYPE
    SYNTAX  DisplayString (SIZE (0..255))
    ACCESS  read-only
    STATUS  mandatory
    DESCRIPTION	"A textual string containing information about the volume."
    ::= { sysVolumeEntry 2 }
sysVolumeFS OBJECT-TYPE
    SYNTAX  DisplayString (SIZE (0..15))
    ACCESS  read-only
    STATUS  mandatory
    DESCRIPTION	"System Volume file system."
    ::= { sysVolumeEntry 3 }
sysVolumeTotalSize OBJECT-TYPE
    SYNTAX  DisplayString (SIZE (0..15))
    ACCESS  read-only
    STATUS  mandatory
    DESCRIPTION	"System Volume total size."
    ::= { sysVolumeEntry 4 }
sysVolumeFreeSize OBJECT-TYPE
    SYNTAX  DisplayString (SIZE (0..15))
    ACCESS  read-only
    STATUS  mandatory
    DESCRIPTION	"System Volume free size."
    ::= { sysVolumeEntry 5 }
sysVolumeStatus OBJECT-TYPE
    SYNTAX  DisplayString (SIZE (0..255))
    ACCESS  read-only
    STATUS  mandatory
    DESCRIPTION	"System Volume status."
    ::= { sysVolumeEntry 6 }

END
